NYMNETWORKS-MIB DEFINITIONS ::= BEGIN

IMPORTS
	enterprises FROM RFC1155-SMI
	OBJECT-TYPE FROM RFC-1212
	DisplayString FROM RFC-1213;

nymnetworks	OBJECT IDENTIFIER ::= {enterprises 25359}

zfs	OBJECT IDENTIFIER ::= {nymnetworks 1}
fs	OBJECT IDENTIFIER ::= {zfs 1}

zfsFilesystemName OBJECT-TYPE
	SYNTAX	DisplayString
	ACCESS	read-only
	STATUS	mandatory
	DESCRIPTION
		"The name of the filesystem."
	::= {fs 1}

zfsFilesystemAvailableKB OBJECT-TYPE
	SYNTAX	GAUGE
	ACCESS	read-only
	STATUS	mandatory
	DESCRIPTION
	         "The number of 1 KB blocks that are available for use."
	::= {fs 2}

zfsFilesystemUsedKB OBJECT-TYPE
	SYNTAX	GAUGE
	ACCESS	read-only
	STATUS	mandatory
	DESCRIPTION
	         "The number of 1 KB blocks that are in use."
	::= {fs 3}

zfsPoolHealth OBJECT-TYPE
	SYNTAX	INTEGER { online(1), degraded(2), faulted(3), unknown(4) }
	ACCESS	read-only
	STATUS	mandatory
	DESCRIPTION
	         "The current health of the containing pool, as reported
		 by zpool status."
	::= {fs 4}

zfsFilesystemAvailableMB OBJECT-TYPE
	SYNTAX	GAUGE
	ACCESS	read-only
	STATUS	mandatory
	DESCRIPTION
	         "The number of 1 MB blocks that are available for use.
		 Useful if zfsFilesystemAvailableKB exceeds a 32 bit
		 integer."
	::= {fs 12}

zfsFilesystemUsedMB OBJECT-TYPE
	SYNTAX	GAUGE
	ACCESS	read-only
	STATUS	mandatory
	DESCRIPTION
	         "The number of 1 MB blocks that are in use Useful if
		 zfsFilesystemUsedKB exceeds a 32 bit integer."
	::= {fs 13}

arc	OBJECT IDENTIFIER ::= {zfs 2}

zfsARCSizeKB OBJECT-TYPE
	SYNTAX	GAUGE
	ACCESS	read-only
	STATUS	mandatory
	DESCRIPTION
	         "The current ARC size in KB."
	::= {arc 1}

zfsARCMetadataSizeKB OBJECT-TYPE
	SYNTAX	GAUGE
	ACCESS	read-only
	STATUS	mandatory
	DESCRIPTION
	         "The amount of ARC space used for metadata storage, in KB."
	::= {arc 2}

zfsARCDataSizeKB OBJECT-TYPE
	SYNTAX	GAUGE
	ACCESS	read-only
	STATUS	mandatory
	DESCRIPTION
	         "The amount of ARC space used for file data storage, in KB."
	::= {arc 3}

zfsARCHits OBJECT-TYPE
	SYNTAX	COUNTER
	ACCESS	read-only
	STATUS	mandatory
	DESCRIPTION
	         "The number of ARC accesses that were cache hits."
	::= {arc 4}

zfsARCMisses OBJECT-TYPE
	SYNTAX	GAUGE
	ACCESS	read-only
	STATUS	mandatory
	DESCRIPTION
	         "The number of ARC accesses that were cache misses."
	::= {arc 5}

l2arc	OBJECT IDENTIFIER ::= {zfs 3}

zfsL2ARCHits OBJECT-TYPE
	SYNTAX	COUNTER
	ACCESS	read-only
	STATUS	mandatory
	DESCRIPTION
	         "The number of L2ARC accesses that were cache hits."
	::= {l2arc 1}

zfsL2ARCMisses OBJECT-TYPE
	SYNTAX	COUNTER
	ACCESS	read-only
	STATUS	mandatory
	DESCRIPTION
	         "The number of L2ARC accesses that were cache misses."
	::= {l2arc 2}

zfsL2ARCReads OBJECT-TYPE
	SYNTAX	COUNTER
	ACCESS	read-only
	STATUS	mandatory
	DESCRIPTION
	         "The number of reads made from L2ARC devices."
	::= {l2arc 3}

zfsL2ARCWrites OBJECT-TYPE
	SYNTAX	COUNTER
	ACCESS	read-only
	STATUS	mandatory
	DESCRIPTION
	         "The number of writes made to L2ARC devices."
	::= {l2arc 4}

io	OBJECT IDENTIFIER ::= {zfs 4}

zfsReadKB OBJECT-TYPE
	SYNTAX	COUNTER
	ACCESS	read-only
	STATUS	mandatory
	DESCRIPTION
	         "The amount of file data read from the ZFS filesystem layer, in KB."
	::= {io 1}

zfsReaddirKB OBJECT-TYPE
	SYNTAX	COUNTER
	ACCESS	read-only
	STATUS	mandatory
	DESCRIPTION
	         "The amount of directory data read from the ZFS filesystem layer, in KB."
	::= {io 2}

zfsWriteKB OBJECT-TYPE
	SYNTAX	COUNTER
	ACCESS	read-only
	STATUS	mandatory
	DESCRIPTION
	         "The amount of file data written to the ZFS filesystem layer, in KB."
	::= {io 3}

END
